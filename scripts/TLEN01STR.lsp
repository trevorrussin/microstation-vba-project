;; TLEN for Loc01 Straight steel curb segments (window + layer).
;; Layer name matches classify output.
(defun C:TLEN01STR (/ ss tl n itm ent obj l lay p1 p2)
  (setq lay "Straight Steel Faced Concrete Curb (18'' Deep)")
  ;; Loc01 keep box (same as verify scripts)
  (setq ss (ssget "C"
                  (list 1028440.0 187390.0 0.0)
                  (list 1028620.0 187530.0 0.0)
                  (list (cons 8 lay))))
  (if (null ss)
    (progn
      (alert "No Straight segments found in Loc01 window.")
      (princ)
    )
    (progn
      (setq tl 0.0
            n (1- (sslength ss)))
      (while (>= n 0)
        (setq ent (entget (setq itm (ssname ss n)))
              obj (cdr (assoc 0 ent))
              l (cond
                  ((= obj "LINE")
                   (distance (cdr (assoc 10 ent)) (cdr (assoc 11 ent))))
                  ((= obj "ARC")
                   (* (cdr (assoc 40 ent))
                      (if (minusp (setq l (- (cdr (assoc 51 ent)) (cdr (assoc 50 ent)))))
                          (+ pi pi l) l)))
                  ((or (= obj "CIRCLE")
                       (= obj "SPLINE")
                       (= obj "POLYLINE")
                       (= obj "LWPOLYLINE")
                       (= obj "ELLIPSE")
                       (= obj "AECC_FEATURE_LINE"))
                   (command "_.area" "_o" itm)
                   (getvar "perimeter"))
                  (T 0.0)))
        (setq tl (+ tl l)
              n (1- n)))
      (alert (strcat "Loc01 Straight — Total length of selected objects is " (rtos tl 2 4)
                     "\nCount: " (itoa (sslength ss))))
      (princ (strcat "\nTLEN01STR total=" (rtos tl 2 4) " count=" (itoa (sslength ss)) "\n"))
    )
  )
  (princ)
)
(princ "\nTLEN01STR loaded. Type TLEN01STR to run.\n")
(princ)
