(progn (vl-load-com)
(alert "East NORTH end\n\nThree corners of the east-north yellow triangle (P1/P2/P3).\n\nPick any 3 corners of the yellow triangle (P1, P2, P3).")
(command "_.ZOOM" "_C" "1028585.0,187451.0" "14.0")
(setq _ask_banner (entmakex (list '(0 . "MTEXT") '(100 . "AcDbEntity") '(8 . "C-ANNO-NPLT") '(62 . 2) '(100 . "AcDbMText") '(10 1028573.000 187463.000 0.0) '(40 . 1.0) '(41 . 28.0) (cons 1 "East NORTH end\\PThree corners of the east-north yellow triangle (P1/P2/P3).\\P\\PPick any 3 corners of the yellow triangle (P1, P2, P3)."))))
(setq _ask_pts nil)
(setq _ask_prev nil)
(setq _p (getpoint "\n1/3 Point 1: "))
(if (null _p) (progn (if _ask_banner (entdel _ask_banner)) (setq f (open "c:/repos/microstation-vba-project/scripts/_acad_ask_result.txt" "w")) (write-line "CANCEL" f) (close f) (exit)))
(setq _ask_pts (cons _p _ask_pts))
(setq _ask_prev _p)
(alert "Next: 2/3 Point 2")
(setq _p (getpoint _ask_prev "\n2/3 Point 2: "))
(if (null _p) (progn (if _ask_banner (entdel _ask_banner)) (setq f (open "c:/repos/microstation-vba-project/scripts/_acad_ask_result.txt" "w")) (write-line "CANCEL" f) (close f) (exit)))
(setq _ask_pts (cons _p _ask_pts))
(alert "Next: 3/3 Point 3 (must differ from 1 and 2)")
(setq _p (getpoint _ask_prev "\n3/3 Point 3 (must differ from 1 and 2): "))
(if (null _p) (progn (if _ask_banner (entdel _ask_banner)) (setq f (open "c:/repos/microstation-vba-project/scripts/_acad_ask_result.txt" "w")) (write-line "CANCEL" f) (close f) (exit)))
(setq _ask_pts (cons _p _ask_pts))
(if _ask_banner (entdel _ask_banner))
(setq _ask_pts (reverse _ask_pts))
(setq f (open "c:/repos/microstation-vba-project/scripts/_acad_ask_result.txt" "w"))
(write-line "OK" f)
(foreach p _ask_pts (write-line (strcat "POINT," (rtos (car p) 2 6) "," (rtos (cadr p) 2 6)) f))
(close f) (princ "\nASK_OK") (princ))
